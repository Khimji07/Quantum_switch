module quantumnet-openros {
  yang-version 1.1;
  namespace "urn:ietf:params:xml:ns:yang:quantumnet-interfaces";
  prefix if;

  organization
    "IETF NETMOD (Network Modeling) Working Group";

  contact
    "WG Web:   <https://www.sartura.hr>
     Editor:   Petar Chichev
               <mailto:petar.cicev@sartura.hr>";

  description
    "This module contains a collection of YANG definitions for
     managing network interfaces.";

    revision 2024-01-11 {
    description
      "Initial revision.";
    reference
      "A YANG Data Model for Interface Management";
    }

    /*
    * Typedefs
    */

    /*
    * Identities
    */

    /*
    * Features
    */

    /*
    * Data nodes
    */

    container switch {
        description
        "Interface parameters.";

        list interface {
        key "name";

        description
            "The list of interfaces on the device.

            The status of an interface is available in this list in the
            operational state.  If the configuration of a
            system-controlled interface cannot be used by the system
            (e.g., the interface hardware present does not match the
            interface type), then the configuration is not applied to
            the system-controlled interface shown in the operational
            state.  If the configuration of a user-controlled interface
            cannot be used by the system, the configured interface is
            not instantiated in the operational state.

            System-controlled interfaces created by the system are
            always present in this list in the operational state,
            whether or not they are configured.";

            leaf name {
                type string;
                description
                "The name of the interface.

                A device MAY restrict the allowed values for this leaf,
                possibly depending on the type of the interface.
                For system-controlled interfaces, this leaf is the
                device-specific name of the interface.

                If a client tries to create configuration for a
                system-controlled interface that is not present in the
                operational state, the server MAY reject the request if
                the implementation does not support pre-provisioning of
                interfaces or if the name refers to an interface that can
                never exist in the system.  A Network Configuration
                Protocol (NETCONF) server MUST reply with an rpc-error
                with the error-tag 'invalid-value' in this case.

                If the device supports pre-provisioning of interface
                configuration, the 'pre-provisioning' feature is
                advertised.

                If the device allows arbitrarily named user-controlled
                interfaces, the 'arbitrary-names' feature is advertised.

                When a configured user-controlled interface is created by
                the system, it is instantiated with the same name in the
                operational state.

                A server implementation MAY map this leaf to the ifName
                MIB object.  Such an implementation needs to use some
                mechanism to handle the differences in size and characters
                allowed between this leaf and ifName.  The definition of
                such a mechanism is outside the scope of this document.";
                reference
                "RFC 2863: The Interfaces Group MIB - ifName";
            }

            leaf description {
                type string;
                description
                "A textual description of the interface.

                A server implementation MAY map this leaf to the ifAlias
                MIB object.  Such an implementation needs to use some
                mechanism to handle the differences in size and characters
                allowed between this leaf and ifAlias.  The definition of
                such a mechanism is outside the scope of this document.

                Since ifAlias is defined to be stored in non-volatile
                storage, the MIB implementation MUST map ifAlias to the
                value of 'description' in the persistently stored
                configuration.";
                reference
                "RFC 2863: The Interfaces Group MIB - ifAlias";
            }

            leaf type {
                type uint16;
                mandatory true;
                description
                "The type of the interface.

                When an interface entry is created, a server MAY
                initialize the type leaf with a valid value, e.g., if it
                is possible to derive the type from the name of the
                interface.

                If a client tries to set the type of an interface to a
                value that can never be used by the system, e.g., if the
                type is not supported or if the type does not match the
                name of the interface, the server MUST reject the request.
                A NETCONF server MUST reply with an rpc-error with the
                error-tag 'invalid-value' in this case.";
                reference
                "RFC 2863: The Interfaces Group MIB - ifType";
            }

            leaf oper-status {
                type enumeration {
                enum up {
                    value 1;
                    description
                    "Ready to pass packets.";
                }
                enum down {
                    value 2;

                    description
                    "The interface does not pass any packets.";
                }
                enum testing {
                    value 3;
                    description
                    "In some test mode.  No operational packets can
                    be passed.";
                }
                enum unknown {
                    value 4;
                    description
                    "Status cannot be determined for some reason.";
                }
                enum dormant {
                    value 5;
                    description
                    "Waiting for some external event.";
                }
                enum not-present {
                    value 6;
                    description
                    "Some component (typically hardware) is missing.";
                }
                enum lower-layer-down {
                    value 7;
                    description
                    "Down due to state of lower-layer interface(s).";
                }
                }
                config false;
                mandatory true;
                description
                "The current operational state of the interface.

                This leaf has the same semantics as ifOperStatus.";
                reference
                "RFC 2863: The Interfaces Group MIB - ifOperStatus";
            }

            leaf if-index {
                type int32 {
                range "1..2147483647";
                }
                config false;
                mandatory true;
                description
                "The ifIndex value for the ifEntry represented by this
                interface.";
                reference
                "RFC 2863: The Interfaces Group MIB - ifIndex";
            }

            leaf phys-address {
                type string;
                config false;
                description
                "The interface's address at its protocol sub-layer.  For
                example, for an 802.x interface, this object normally
                contains a Media Access Control (MAC) address.  The
                interface's media-specific modules must define the bit
                and byte ordering and the format of the value of this
                object.  For interfaces that do not have such an address
                (e.g., a serial line), this node is not present.";
                reference
                "RFC 2863: The Interfaces Group MIB - ifPhysAddress";
            }

            leaf speed {
                type uint64;
                units "bits/second";
                config false;
                description
                    "An estimate of the interface's current bandwidth in bits
                    per second.  For interfaces that do not vary in
                    bandwidth or for those where no accurate estimation can
                    be made, this node should contain the nominal bandwidth.
                    For interfaces that have no concept of bandwidth, this
                    node is not present.";
                reference
                "RFC 2863: The Interfaces Group MIB -
                            ifSpeed, ifHighSpeed";
            }
        }

    }
}
